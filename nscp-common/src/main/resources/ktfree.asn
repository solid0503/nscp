KTFreeFormatData DEFINITIONS ::= BEGIN

	KT-FreeFormatData  ::=  SEQUENCE {
		cdrVersion       				[1] OCTET STRING (SIZE(4)),
		serviceKey       				[2] INTEGER(0..65535) OPTIONAL,
		cdrType           				[3] OCTET STRING (SIZE(1)) OPTIONAL,
		chargingNumber   				[4] OCTET STRING (SIZE(4..32)) OPTIONAL,
		iMSI              				[5] OCTET STRING (SIZE(15)) OPTIONAL,
		subscriber-IP-Address 				[6] OCTET STRING (SIZE(4..32)) OPTIONAL,
		wSType 				[7] INTEGER		OPTIONAL,
		winServiceName 				[8] OCTET STRING (SIZE(2..10)) OPTIONAL,
		aPN 				[9] OCTET STRING (SIZE(2..63)) OPTIONAL,
		accountingStatusType				[10] OCTET STRING (SIZE(1)) OPTIONAL,
		nAS-IP-Address 				[11] OCTET STRING (SIZE(4..32)) OPTIONAL,
		sGSN-IP-Address 				[12] OCTET STRING (SIZE(4..32)) OPTIONAL,
		pDP-Type 		 	 	[13] OCTET STRING (SIZE(2)) OPTIONAL,
		nASAPI 			 	[14] OCTET STRING (SIZE(4)) OPTIONAL,
		chargingCharacteristic 			 	[15] OCTET STRING (SIZE(4)) OPTIONAL,
		sGSN-MCC-MNC 				[16] OCTET STRING (SIZE(1..6)) OPTIONAL,
		gPRSNegotiatedQoSProfile 			[17] OCTET STRING (SIZE(1..31)) OPTIONAL,
		chargingId 				[18] OCTET STRING (SIZE(1..10)) OPTIONAL,
		iMSChargingIdentifier 				[19] OCTET STRING (SIZE(4..80)) OPTIONAL,
		originating-Inter-Operator-Identifier	 	[20] OCTET STRING (SIZE(8)) OPTIONAL,
		terminating-Inter-Operator-Identifier		[21] OCTET STRING (SIZE(8)) OPTIONAL,
		serviceStart3GPPUserLocationInfo 		[22] OCTET STRING (SIZE(1..16)) OPTIONAL,
		serviceTerminating3GPPUserLocationInfo 	[23] OCTET STRING (SIZE(1..16)) OPTIONAL,
		nASReleaseIndicator 				[24] OCTET STRING (SIZE(2)) OPTIONAL,
		applicationReleaseIndicator				[25] OCTET STRING (SIZE(4)) OPTIONAL,
		packetSessionStartTime 				[26] OCTET STRING (SIZE(14)) OPTIONAL,
		packetSessionEndTime 			 	[27] OCTET STRING (SIZE(14)) OPTIONAL,
		accumulatedUploadDataOctets 		[28] INTEGER OPTIONAL,
		accumulatedDownloadDataOctets 		[29] INTEGER OPTIONAL,
		totalTimeDuration 				[30] INTEGER OPTIONAL,
		serviceCategoryId 				[31] INTEGER OPTIONAL,
		serviceChargingType 				[32] OCTET STRING (SIZE(3)) OPTIONAL,
		serviceChargingRate 				[33] OCTET STRING (SIZE(3)) OPTIONAL,
		serviceCallType 				[34] OCTET STRING (SIZE(1)) OPTIONAL,
		serviceCallingInformation 				[35] OCTET STRING (SIZE(2..30)) OPTIONAL,
		serviceCalledInformation 				[36] OCTET STRING (SIZE(2..30)) OPTIONAL,
		serviceStartTime 				[37] OCTET STRING (SIZE(14)) OPTIONAL,
		serviceEndTime 				[38] OCTET STRING (SIZE(14)) OPTIONAL,
		serviceUploadDataOctets 				[39] INTEGER OPTIONAL,
		serviceDownloadDataOctets 			[40] INTEGER OPTIONAL,
		serviceContentsCount 				[41] INTEGER OPTIONAL,
		serviceContentsType 				[42] OCTET STRING (SIZE(2)) OPTIONAL,
		serviceTimeDuration 				[43] INTEGER OPTIONAL,
		servicePrepaidAirTimeCharge 		[44] INTEGER OPTIONAL,
		servicePrepaidPacketCharge 			[45] INTEGER OPTIONAL,
		servicePrepaidCountCharge 			[46] INTEGER OPTIONAL,
		servicePrepaidInformationCharge		[47] INTEGER OPTIONAL,
		service3GPPGPRSNegotiatedQoSProfile 	[48] OCTET STRING (SIZE(1..31)) OPTIONAL,
		servicePricePlan					[49] OCTET STRING (SIZE(2)) OPTIONAL,
        subscriberIPv6Address               [50] OCTET STRING (SIZE(4..40)) OPTIONAL,
        roamingServiceStartTime             [51] OCTET STRING (SIZE(14)) OPTIONAL,
        roamingServiceEndTime               [52] OCTET STRING (SIZE(14)) OPTIONAL,
        summerTime                          [53] OCTET STRING (SIZE(1)) OPTIONAL
	}

END
